Attribute VB_Name = "ThisDrawing"
Attribute VB_Base = "0{149DD748-EA85-45A6-93C5-AC50D0260C98}"
Attribute VB_GlobalNameSpace = False
Attribute VB_Creatable = False
Attribute VB_PredeclaredId = True
Attribute VB_Exposed = True
Attribute VB_TemplateDerived = False
Attribute VB_Customizable = True
Option Explicit
Const pi As Double = 3.14159265358979
Public Sub RectChamfer(x As Double, y As Double, a As Double, b As Double, c1 As Double, c2 As Double)
Dim pline As AcadLWPolyline
Dim points(0 To 15) As Double
points(0) = x: points(1) = y + c1 * Sgn(b)
points(2) = x: points(3) = y + b - c2 * Sgn(b)
points(4) = x + c1 * Sgn(a): points(5) = y + b
points(6) = x + a - c2 * Sgn(a): points(7) = y + b
points(8) = x + a: points(9) = y + b - c1 * Sgn(b)
points(10) = x + a: points(11) = y + c2 * Sgn(b)
points(12) = x + a - c1 * Sgn(a): points(13) = y
points(14) = x + c2 * Sgn(a): points(15) = y
Set pline = ThisDrawing.ModelSpace.AddLightWeightPolyline(points)
pline.Closed = True
pline.Update
End Sub

Public Sub RectFillet(x As Double, y As Double, a As Double, b As Double, f As Double)
Dim pline As AcadLWPolyline
Dim points(0 To 15) As Double
points(0) = x: points(1) = y + f * Sgn(b)
points(2) = x: points(3) = y + b - f * Sgn(b)
points(4) = x + f * Sgn(a): points(5) = y + b
points(6) = x + a - f * Sgn(a): points(7) = y + b
points(8) = x + a: points(9) = y + b - f * Sgn(b)
points(10) = x + a: points(11) = y + f * Sgn(b)
points(12) = x + a - f * Sgn(a): points(13) = y
points(14) = x + f * Sgn(a): points(15) = y
Set pline = ThisDrawing.ModelSpace.AddLightWeightPolyline(points)
pline.Closed = True
Call pline.SetBulge(1, -Tan(pi / 8))
Call pline.SetBulge(3, -Tan(pi / 8))
Call pline.SetBulge(5, -Tan(pi / 8))
Call pline.SetBulge(7, -Tan(pi / 8))
pline.Update
End Sub

Public Sub Keyboard(column As Integer, row As Integer, width As Double, height As Double, hspace As Double, vspace As Double)
Dim c As Integer, r As Integer
Dim x As Double, y As Double, f As Double
If width < height Then f = width / 10 Else f = height / 10
For r = 0 To row - 1
For c = 0 To column - 1
x = c * (width + hspace)
y = r * (height + vspace)
Call RectFillet(x, y, width, height, f)
Next
Next
End Sub
